EUTRA-RRC-Definitions DEFINITIONS AUTOMATIC TAGS ::=

BEGIN


BCCH-BCH-Message ::= SEQUENCE {
 message     BCCH-BCH-MessageType
}

BCCH-BCH-MessageType ::=      MasterInformationBlock

BCCH-DL-SCH-Message ::= SEQUENCE {
 message     BCCH-DL-SCH-MessageType
}

BCCH-DL-SCH-MessageType ::= CHOICE {
 c1      CHOICE {
  systemInformation      SystemInformation,
  systemInformationBlockType1    SystemInformationBlockType1
 },
 messageClassExtension SEQUENCE {}
}

MCCH-Message ::=   SEQUENCE {
 message     MCCH-MessageType
}

MCCH-MessageType ::= CHOICE {
 c1       CHOICE {
  mbsfnAreaConfiguration-r9  MBSFNAreaConfiguration-r9
 },
 messageClassExtension SEQUENCE {}
}


PCCH-Message ::= SEQUENCE {
 message     PCCH-MessageType
}

PCCH-MessageType ::= CHOICE {
 c1      CHOICE {
  paging         Paging
 },
 messageClassExtension SEQUENCE {}
}


DL-CCCH-Message ::= SEQUENCE {
 message     DL-CCCH-MessageType
}

DL-CCCH-MessageType ::= CHOICE {
 c1      CHOICE {
  rrcConnectionReestablishment   RRCConnectionReestablishment,
  rrcConnectionReestablishmentReject  RRCConnectionReestablishmentReject,
  rrcConnectionReject      RRCConnectionReject,
  rrcConnectionSetup      RRCConnectionSetup
 },
 messageClassExtension SEQUENCE {}
}


DL-DCCH-Message ::= SEQUENCE {
 message     DL-DCCH-MessageType
}

DL-DCCH-MessageType ::= CHOICE {
 c1      CHOICE {
  csfbParametersResponseCDMA2000   CSFBParametersResponseCDMA2000,
  dlInformationTransfer     DLInformationTransfer,
  handoverFromEUTRAPreparationRequest  HandoverFromEUTRAPreparationRequest,
  mobilityFromEUTRACommand    MobilityFromEUTRACommand,
  rrcConnectionReconfiguration   RRCConnectionReconfiguration,
  rrcConnectionRelease     RRCConnectionRelease,
  securityModeCommand      SecurityModeCommand,
  ueCapabilityEnquiry      UECapabilityEnquiry,
  counterCheck       CounterCheck,
  ueInformationRequest-r9     UEInformationRequest-r9,
  spare6 NULL, spare5 NULL, spare4 NULL,
  spare3 NULL, spare2 NULL, spare1 NULL
 },
 messageClassExtension SEQUENCE {}
}

UL-CCCH-Message ::= SEQUENCE {
 message     UL-CCCH-MessageType
}

UL-CCCH-MessageType ::= CHOICE {
 c1      CHOICE {
  rrcConnectionReestablishmentRequest  RRCConnectionReestablishmentRequest,
  rrcConnectionRequest     RRCConnectionRequest
 },
 messageClassExtension SEQUENCE {}
}


UL-DCCH-Message ::= SEQUENCE {
 message     UL-DCCH-MessageType
}

UL-DCCH-MessageType ::= CHOICE {
 c1      CHOICE {
  csfbParametersRequestCDMA2000   CSFBParametersRequestCDMA2000,
  measurementReport      MeasurementReport,
  rrcConnectionReconfigurationComplete RRCConnectionReconfigurationComplete,
  rrcConnectionReestablishmentComplete RRCConnectionReestablishmentComplete,
  rrcConnectionSetupComplete    RRCConnectionSetupComplete,
  securityModeComplete     SecurityModeComplete,
  securityModeFailure      SecurityModeFailure,
  ueCapabilityInformation     UECapabilityInformation,
ulHandoverPreparationTransfer   ULHandoverPreparationTransfer,
  ulInformationTransfer     ULInformationTransfer,
  counterCheckResponse     CounterCheckResponse,
  ueInformationResponse-r9    UEInformationResponse-r9,
  proximityIndication-r9     ProximityIndication-r9,
    spare3 NULL, spare2 NULL, spare1 NULL
 },
 messageClassExtension SEQUENCE {}
}


CounterCheck ::=   SEQUENCE {
 rrc-TransactionIdentifier   RRC-TransactionIdentifier,
 criticalExtensions     CHOICE {
  c1         CHOICE {
   counterCheck-r8      CounterCheck-r8-IEs,
   spare3 NULL, spare2 NULL, spare1 NULL
  },
  criticalExtensionsFuture   SEQUENCE {}
 }
}

CounterCheck-r8-IEs ::= SEQUENCE {
 drb-CountMSB-InfoList    DRB-CountMSB-InfoList,
 nonCriticalExtension    CounterCheck-v8a0-IEs       OPTIONAL
}

CounterCheck-v8a0-IEs ::= SEQUENCE {
 lateNonCriticalExtension   OCTET STRING      OPTIONAL, -- Need OP
 nonCriticalExtension    SEQUENCE {}       OPTIONAL -- Need OP
}

DRB-CountMSB-InfoList ::=  SEQUENCE (SIZE (1..maxDRB)) OF DRB-CountMSB-Info

DRB-CountMSB-Info ::= SEQUENCE {
 drb-Identity     DRB-Identity,
 countMSB-Uplink     INTEGER(0..33554431),
 countMSB-Downlink    INTEGER(0..33554431)
}

CSFBParametersRequestCDMA2000 ::= SEQUENCE {
 criticalExtensions     CHOICE {
  csfbParametersRequestCDMA2000-r8 CSFBParametersRequestCDMA2000-r8-IEs,
  criticalExtensionsFuture   SEQUENCE {}
 }
}

CSFBParametersRequestCDMA2000-r8-IEs ::= SEQUENCE {
 nonCriticalExtension    CSFBParametersRequestCDMA2000-v8a0-IEs      OPTIONAL
}

CSFBParametersRequestCDMA2000-v8a0-IEs ::= SEQUENCE {
 lateNonCriticalExtension   OCTET STRING      OPTIONAL,
 nonCriticalExtension    SEQUENCE {}       OPTIONAL
}

CSFBParametersResponseCDMA2000 ::= SEQUENCE {
 rrc-TransactionIdentifier   RRC-TransactionIdentifier,
 criticalExtensions      CHOICE {
  csfbParametersResponseCDMA2000-r8  CSFBParametersResponseCDMA2000-r8-IEs,
  criticalExtensionsFuture    SEQUENCE {}
 }
}

CSFBParametersResponseCDMA2000-r8-IEs ::= SEQUENCE {
 rand         RAND-CDMA2000,
 mobilityParameters      MobilityParametersCDMA2000,
 nonCriticalExtension     CSFBParametersResponseCDMA2000-v8a0-IEs      OPTIONAL
}

CSFBParametersResponseCDMA2000-v8a0-IEs ::= SEQUENCE {
 lateNonCriticalExtension   OCTET STRING      OPTIONAL, -- Need OP
 nonCriticalExtension    SEQUENCE {}       OPTIONAL -- Need OP
}

DLInformationTransfer ::=   SEQUENCE {
 rrc-TransactionIdentifier   RRC-TransactionIdentifier,
 criticalExtensions     CHOICE {
  c1         CHOICE {
   dlInformationTransfer-r8   DLInformationTransfer-r8-IEs,
   spare3 NULL, spare2 NULL, spare1 NULL
  },
  criticalExtensionsFuture   SEQUENCE {}
 }
}

DLInformationTransfer-r8-IEs ::= SEQUENCE {
 dedicatedInfoType     CHOICE {
  dedicatedInfoNAS     DedicatedInfoNAS,
  dedicatedInfoCDMA2000-1XRTT   DedicatedInfoCDMA2000,
  dedicatedInfoCDMA2000-HRPD   DedicatedInfoCDMA2000
 },
 nonCriticalExtension    DLInformationTransfer-v8a0-IEs      OPTIONAL
}

DLInformationTransfer-v8a0-IEs ::= SEQUENCE {
 lateNonCriticalExtension   OCTET STRING      OPTIONAL, -- Need OP
 nonCriticalExtension    SEQUENCE {}       OPTIONAL -- Need OP
}


HandoverFromEUTRAPreparationRequest ::= SEQUENCE {
 rrc-TransactionIdentifier  RRC-TransactionIdentifier,
 criticalExtensions     CHOICE {
  c1         CHOICE {
   handoverFromEUTRAPreparationRequest-r8
            HandoverFromEUTRAPreparationRequest-r8-IEs,
   spare3 NULL, spare2 NULL, spare1 NULL
  },
  criticalExtensionsFuture   SEQUENCE {}
 }
}

HandoverFromEUTRAPreparationRequest-r8-IEs ::= SEQUENCE {
 cdma2000-Type     CDMA2000-Type,
 rand       RAND-CDMA2000    OPTIONAL,  -- Cond cdma2000-Type
 mobilityParameters    MobilityParametersCDMA2000 OPTIONAL,  -- Cond cdma2000-Type
 nonCriticalExtension    HandoverFromEUTRAPreparationRequest-v890-IEs OPTIONAL
}

HandoverFromEUTRAPreparationRequest-v890-IEs ::= SEQUENCE {
 lateNonCriticalExtension   OCTET STRING    OPTIONAL, -- Need OP
 nonCriticalExtension    HandoverFromEUTRAPreparationRequest-v920-IEs OPTIONAL
}

HandoverFromEUTRAPreparationRequest-v920-IEs ::= SEQUENCE {
 concurrPrepCDMA2000-HRPD-r9  BOOLEAN      OPTIONAL, -- Cond cdma2000-Type
 nonCriticalExtension    SEQUENCE {}     OPTIONAL -- Need OP
}

MasterInformationBlock ::=   SEQUENCE {
 dl-Bandwidth      ENUMERATED {
           n6, n15, n25, n50, n75, n100},
 phich-Config      PHICH-Config,
 systemFrameNumber     BIT STRING (SIZE (8)),
 spare        BIT STRING (SIZE (10))
}

MBSFNAreaConfiguration-r9 ::=  SEQUENCE {
 commonSF-Alloc-r9     CommonSF-AllocPatternList-r9,
 commonSF-AllocPeriod-r9    ENUMERATED {
            rf4, rf8, rf16, rf32, rf64, rf128, rf256},
 pmch-InfoList-r9     PMCH-InfoList-r9,
 nonCriticalExtension    MBSFNAreaConfiguration-v930-IEs   OPTIONAL
}

MBSFNAreaConfiguration-v930-IEs ::= SEQUENCE {
 lateNonCriticalExtension   OCTET STRING      OPTIONAL, -- Need OP
 nonCriticalExtension    SEQUENCE {}       OPTIONAL -- Need OP
}

CommonSF-AllocPatternList-r9 ::= SEQUENCE (SIZE (1..maxMBSFN-Allocations)) OF MBSFN-SubframeConfig

MeasurementReport ::=    SEQUENCE {
 criticalExtensions     CHOICE {
  c1         CHOICE{
   measurementReport-r8    MeasurementReport-r8-IEs,
   spare7 NULL,
   spare6 NULL, spare5 NULL, spare4 NULL,
   spare3 NULL, spare2 NULL, spare1 NULL
  },
  criticalExtensionsFuture   SEQUENCE {}
 }
}

Handover ::=      SEQUENCE {
 targetRAT-MessageContainer   OCTET STRING,
 nas-SecurityParamFromEUTRA   OCTET STRING (SIZE (1))  OPTIONAL,   -- Cond UTRAGERAN
 systemInformation     SI-OrPSI-GERAN    OPTIONAL -- Cond PSHO
}

InterFreqCarrierFreqInfo ::= SEQUENCE {
 dl-CarrierFreq      ARFCN-ValueEUTRA,
 q-RxLevMin       Q-RxLevMin,
 p-Max        P-Max       OPTIONAL,  -- Need OP
 t-ReselectionEUTRA     T-Reselection,
 t-ReselectionEUTRA-SF    SpeedStateScaleFactors   OPTIONAL,  -- Need OP
 threshX-High      ReselectionThreshold,
 threshX-Low       ReselectionThreshold,
 allowedMeasBandwidth    AllowedMeasBandwidth,
 presenceAntennaPort1    PresenceAntennaPort1,
 cellReselectionPriority    CellReselectionPriority   OPTIONAL,  -- Need OP
 neighCellConfig      NeighCellConfig,
 q-OffsetFreq      Q-OffsetRange     DEFAULT dB0,
 interFreqNeighCellList    InterFreqNeighCellList   OPTIONAL,   -- Need OR
 interFreqBlackCellList    InterFreqBlackCellList   OPTIONAL,   -- Need OR
 ...,
 [[ q-QualMin-r9     Q-QualMin-r9     OPTIONAL,  -- Need OP
    threshX-Q-r9     SEQUENCE {
        threshX-HighQ-r9    ReselectionThresholdQ-r9,
        threshX-LowQ-r9     ReselectionThresholdQ-r9
    }                OPTIONAL  -- Cond RSRQ
 ]]
}

UE-TimersAndConstants ::=   SEQUENCE {
 t300        ENUMERATED {
           ms100, ms200, ms300, ms400, ms600, ms1000, ms1500,
           ms2000},
 t301        ENUMERATED {
           ms100, ms200, ms300, ms400, ms600, ms1000, ms1500,
           ms2000},
 t310        ENUMERATED {
           ms0, ms50, ms100, ms200, ms500, ms1000, ms2000},
 n310        ENUMERATED {
           n1, n2, n3, n4, n6, n8, n10, n20},
 t311        ENUMERATED {
           ms1000, ms3000, ms5000, ms10000, ms15000,
           ms20000, ms30000},
 n311        ENUMERATED {
           n1, n2, n3, n4, n5, n6, n8, n10},
 ...
}

SupportedBandUTRA-TDD768 ::=  ENUMERATED {
          a, b, c, d, e, f, g, h, i, j, k, l, m, n,
          o, p, ...}

maxBands     INTEGER ::= 64 -- Maximum number of bands listed in EUTRA UE caps

IMSI-Digit ::=      INTEGER (0..9)

RRCConnectionReconfiguration-r8-IEs ::= SEQUENCE {
 measConfig       MeasConfig      OPTIONAL, -- Need ON
 mobilityControlInfo     MobilityControlInfo    OPTIONAL, -- Cond HO
 dedicatedInfoNASList    SEQUENCE (SIZE(1..maxDRB)) OF
           DedicatedInfoNAS   OPTIONAL, -- Cond nonHO
 radioResourceConfigDedicated  RadioResourceConfigDedicated OPTIONAL, -- Cond HO-toEUTRA
 securityConfigHO     SecurityConfigHO    OPTIONAL, -- Cond HO
 nonCriticalExtension    RRCConnectionReconfiguration-v890-IEs OPTIONAL
}

PresenceAntennaPort1 ::=    BOOLEAN

MobilityParametersCDMA2000 ::=   OCTET STRING

CSFBParametersResponseCDMA2000-r8-IEs ::= SEQUENCE {
 mobilityParameters      MobilityParametersCDMA2000
}

CellInfoGERAN-r9 ::=    SEQUENCE {
 systemInformation-r9    SystemInfoListGERAN
}

SystemInfoListGERAN ::=    SEQUENCE (SIZE (1..3)) OF
          OCTET STRING (SIZE (1..23))

SIB-MappingInfo ::= SEQUENCE (SIZE (0..maxSIB-1)) OF SIB-Type

SIB-Type ::=      ENUMERATED {
          sibType3, sibType4, sibType5, sibType6,
          sibType7, sibType8, sibType9, sibType10,
          sibType11, sibType12-v920, sibType13-v920, spare5,
          spare4, spare3, spare2, spare1, ...}

PUCCH-ConfigDedicated-v1020 ::=             SEQUENCE {
    n1PUCCH-AN-CS-List-r10                      SEQUENCE (SIZE (1..2)) OF N1PUCCH-AN-CS-r10
}
N1PUCCH-AN-CS-r10        ::= SEQUENCE (SIZE (1..4)) OF INTEGER (0..2047)

SecurityCapability ::=                      SEQUENCE {
      cipheringAlgorithmCap                      BIT STRING {
                                                 -- For each bit value "0" means false/ not supported
                                                      spare15(0),
                                                      spare14(1),
                                                      spare13(2),
                                                      spare12(3),
                                                      spare11(4),
                                                      spare10(5),
                                                      spare9(6),
                                                      spare8(7),
                                                      spare7(8),
                                                      spare6(9),
                                                      spare5(10),
                                                      spare4(11),
                                                      spare3(12),
                                                      uea2(13),
                                                      uea1(14),
                                                      uea0(15)
                                                      }     (SIZE (16))
}

IMSI-DS-41 ::=                               OCTET STRING (SIZE (5..7))

RRCConnectionSetupComplete-v690ext-IEs ::= SEQUENCE {
      -- User equipment IEs
          ueCapabilityContainer                      BIT STRING
                                                          (CONTAINING UE-CapabilityContainer-IEs) OPTIONAL
}

SystemInformationBlockType2 ::=              SEQUENCE {
      ac-BarringInfo                              SEQUENCE {
          ac-BarringForEmergency                       BOOLEAN,
          ac-BarringForMO-Signalling                   AC-BarringConfig                        OPTIONAL,       -- Need OP
          ac-BarringForMO-Data                         AC-BarringConfig                        OPTIONAL        -- Need OP
      }                                                                                        OPTIONAL,       -- Need OP
      radioResourceConfigCommon                   RadioResourceConfigCommonSIB,
      ue-TimersAndConstants                       UE-TimersAndConstants,
      freqInfo                                    SEQUENCE {
          ul-CarrierFreq                               ARFCN-ValueEUTRA                        OPTIONAL,       -- Need OP
          ul-Bandwidth                                 ENUMERATED {n6, n15, n25, n50, n75, n100}
                                                                                               OPTIONAL,       -- Need OP
          additionalSpectrumEmission                   AdditionalSpectrumEmission
      },
      mbsfn-SubframeConfigList                    MBSFN-SubframeConfigList                     OPTIONAL,      -- Need OR
      timeAlignmentTimerCommon                    TimeAlignmentTimer,
      ...,
      lateNonCriticalExtension               OCTET STRING (CONTAINING SystemInformationBlockType2-v8h0-IEs)
                              OPTIONAL,       -- Need OP
      [[   ssac-BarringForMMTEL-Voice-r9               AC-BarringConfig                        OPTIONAL,       -- Need OP
          ssac-BarringForMMTEL-Video-r9                AC-BarringConfig                        OPTIONAL        -- Need OP
      ]],
      [[   ac-BarringForCSFB-r10                       AC-BarringConfig                   OPTIONAL        -- Need OP
      ]]
}
END
EUTRA-RRC2-Definitions DEFINITIONS AUTOMATIC TAGS ::=
BEGIN
DRB-CountMSB-InfoList ::=  SEQUENCE (SIZE (1..maxBands)) OF DRB-CountMSB-Info

maxBands     INTEGER ::= 64 -- Maximum number of bands listed in EUTRA UE caps

AccessClassBarredList ::=                   SEQUENCE (SIZE (maxBands)) OF AccessClassBarred

InterRAT-UE-RadioAccessCapability ::= SEQUENCE {
  gsm-Classmark2                                GSM-Classmark2,
  gsm-Classmark3                                GSM-Classmark3
}
GSM-Classmark2 ::=                     OCTET STRING (SIZE (5))
GSM-Classmark3 ::=                     OCTET STRING (SIZE (1..32))

UE-RadioAccessCapability-v690ext ::= SEQUENCE {
         physicalchannelcapability-edch   PhysicalChannelCapability-edch-r6,
         -- TABULAR: deviceType is MD in tabular description
         -- Default value is 'doesBenefitFromBatteryConsumptionOptimisation'
         deviceType       ENUMERATED { doesNotBenefitFromBatteryConsumptionOptimisation } OPTIONAL
}
END
